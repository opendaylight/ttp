/*
 * Copyright (c) 2014 Brocade Communications Systems others. All rights reserved.
 *
 * This program and the accompanying materials are made available under the
 * terms of the Eclipse Public License v1.0 which accompanies this distribution,
 * and is available at http://www.eclipse.org/legal/epl-v10.html
 */

module onf-ttp {
  namespace "urn:onf:ttp";
  prefix ttp;

  import openflow-extensible-match {prefix oxm;}
  //import openflow-instruction {prefix ofi;}
  import openflow-types {prefix oft;}

  revision 2014-07-11 {
    description "ONF TTP schema 2014/07/11";
  }

  grouping name-property {
    description "denotes something that has a name, which is a string";

    leaf name {
      type string;
    }
  }

  grouping opt-tag-property {
    description "denotes strings that represent optional functionality in the TTP";

    leaf opt-tag {
      type string;
    }
  }

  grouping doc-property {
    description "denotes something that has documentation as a list of strings";

    leaf-list doc {
      type string;
    }
  }

  grouping universal-TTP-properties {
    description "these properties are applicable to all objects in TTPs";

    uses name-property;
    uses opt-tag-property;
    uses doc-property;
  }


  grouping type-property {
    description "denotes something that has a type identified with a string";

    leaf type {
      type string;
    }
  }

  grouping NDM_metadata-properties {
    description "metadata about an NDM (or TTP)";

    leaf authority {
       type string;
    }

    leaf OF_protocol_version {
       type string;
    }

    leaf version {
       type string;
    }

    uses type-property;
    uses universal-TTP-properties;
  }

  grouping table-type-pattern-properties {
    container NDM_metadata {
      uses NDM_metadata-properties;
    }

    list identifiers {
      uses universal-TTP-properties;
      leaf var {
        type string;
      }
      leaf range {
        type string;
      }
    }

    list features {
      uses universal-TTP-properties;
      leaf feature {
        type string;
      }
    }

    list table_map { // intentionally not using the "univ TTP props"
      key name;
      leaf name {
        type string;
      }
      leaf number {
        type uint8;
      }
    }

    container meter_table {
      list meter_types {
        uses universal-TTP-properties;
        leaf type {
          type enumeration {
            enum DROP;
            enum DSCP_REMARK;
            //TODO: what are the others?
          }
        }
        leaf rate {
          type string;
          //TODO: should be min/max?
        }
        leaf burst {
          type string;
          //TODO: should be min/max?
        }
      }
      list built_in_meters {
        uses universal-TTP-properties;
        leaf meter_id {
          type uint32; //TODO: right int?
        }
        leaf rate {
          type uint32; //TODO: right int?
        }
        leaf burst {
          type uint32; //TODO: right int?
        }
      }
    }

    list flow_tables {
      //TODO: can inner types also have the univ TTP properties?
      uses universal-TTP-properties;
      list flow_mod_types {
        list match_set {
          leaf field {
            type identityref {
              base oxm:match-field;
            }
          }
          leaf wc_type {
            description "Wildcard type";
            type enumeration {
              enum all_or_none;
              enum none;
              //TODO: are there more?
            }
          }
        }
        container instruction_set {
          list exactly_one {
            list option { //TODO: this should be an anonymous list, but I don't know how
              leaf instruction {
                type identityref {
                  base oft:instruction-base;
                }
              }
              //TODO: need a leaf for the conditional instruction parameters
            }
          }
        }
      }
    }

    list group_entry_types {
      //TODO: model
    }

    list packet_out {
      uses universal-TTP-properties;
      //TODO: model
    }

    list parameters {
      uses universal-TTP-properties;
      uses type-property;
    }

    // We wanted: "flow_paths": ["path": ["table1", ["table2"] ] ]
    // We did: "flow_paths": ["path": ["table1", "[table2]" ] ]
    list flow_paths {
      uses universal-TTP-properties;
      leaf-list path {
        description "a list of strings each of which must be the name of a
                     table from the table_map or the name of a table in square
                     brackets.";
        type string;
      }
    }

    container security {
      uses universal-TTP-properties;
    }
  }

  container opendaylight-ttps {
    container table-type-patterns {
      list table-type-pattern {
        uses table-type-pattern-properties;
      }
    }
    description "The global TTP registry for OpenDaylight";
  }
}
